# EPSRequirements

## EPS-3.01: Power Generation (Informational)
The EPS shall generate power using solar panels mounted on the satellite body

### EPS-4.01: Solar Input Measurement (Functional)
The EPS shall read current and voltage measurements from each panel individually
- Rationale: Individual reading allows us to confirm the optimal functioning of each panel and can also be used for course attitude estimation as a sanity check

### EPS-4.02: MPPT (Functional)
The EPS should implement maximum power point tracking and control techniques for maximising power generation

## EPS-3.02: Battery (Informational)
The EPS shall include batteries for energy storage

### #12: Battery Capacity (Functional)
The battery capacity shall be atleast:
- TBD Wh for Target
- TBD Wh for Chaser

### #13: Depth of Discharge (DoD) (Functional)
The maximum DoD shall be:
- TBD % on Target
- TBD % on Chaser

### #14: C-Rating (Functional)
The battery pack should have a minimum C-rating of:
- TBD on Target
- TBD on Chaser

### #15: Battery Management (Functional)
CubeSats shall incorporate battery circuit protection for charging/discharging to avoid unbalanced cell conditions. Additional manufacturer documentation and/or testing will be required for modified, customized, or non-UL-listed cells
- Rationale: CDS Rev14 Electrical Specifications

### #25: Battery Heater (Functional)
The EPS shall include a battery heater which will regulate the battery temperature within TBD range

## EPS-3.03: Power Consumption (Functional)
The EPS shall support power consumption of all onboard systems

## EPS-3.04: Size/Volume (Functional)
The EPS shall occupy not more than 0.32 U on Target and 0.52 U on Chaser

## EPS-3.05: Mass (Functional)
The EPS shall not weigh more than 713 g (Target) and 778 g (Chaser)

## EPS-3.07: Power Sharing Post-Docking (Functional)
The EPS shall have capability to share power through docking port in docked state

### EPS-3.06: Power Sharing Pre-Separation (Functional)
The EPS shall have capability of power sharing in combined 6U state pre-separation

## EPS-3.09: Communication with OBC (Functional)
The EPS shall communicate with the OBC to provide HM data and receive commands

### #29: Heartbeat (Functional)

### #30: Health Monitoring Data (Functional)
The HM Data shall include the Solar Panel Currents, Voltages and Power, Vmp computed, Battery Voltage, Battery SoC, Line Voltage, Line Current etc. (not exhaustive)

## EPS-3.10: Independent Power Cycling (Functional)
The EPS shall have the capability to power cycle each subsystem independently

### #26: Voltage and Current Monitoring (Functional)
The EPS shall read the voltage and current drawn from each subsystem independently to monitor over-voltage and over-current conditions

### #27: Current Limiting (Functional)
The EPS shall have a current limiter that latches the maximum current drawn to prevent over-current conditions

### #28: Subystem Power Reset Counter (Functional)
The EPS shall keep track of faults and power cyles and communicate this to the OBC

## #17: Operational State Pre-Deployment (Functional)
To prevent CubeSat from activating any powered functions, the CubeSat power system shall be at a power off state from the time of delivery to the launch vehicel through on-orbit deployment

### #18: Battery Protection Power Status (Informational)
Powered-on battery protection circuitry may be permitted
- Rationale: CDS Rev14 Electrical Specifications

## #19: Remove Before Flight (Functional)
The CubeSat shall include an RBF pin, which cuts all power to the satellite once it is inserted into the satellite

### #20: Removal (Functional)
Access to the CubeSat is not guaranteed during or after integration. The RBF pin shall be removed from the CubeSat before integration into the dispenser, if the dispenser does not have access ports.

### #21: Mechanical (Functional)
The RBF pin shall protrude no more than 6.5 mm from the CubeSat rail surface when it is fully inserted into the satellite

### #22: Location (Functional)
The RBF pin and all CubeSat umbilical connectors shall be within the designated access port locations if available on the CubeSat’s dispenser

## #31: Charging Port (Functional)
The EPS shall have a charging port for battery charging and powering the system during on-ground testing
